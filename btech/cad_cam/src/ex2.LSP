(defun c:ex2()
  (setq r1(getint "enter the value for radius"))
  (setq c2 10)
  (setq d1(* 2 r1))
  (setq l5 d1)
  (setq l3(* 1.5 d1))
  (setq l6(* 10 d1))
  (setq l1(- l6 d1))
  (setq l4(+ l3 d1))
  (setq c0(getpoint "get the point for circle"))
  (setq c1(list (- (car c0) r1) (cadr c0)))
  (command "circle" c0 r1 )
  (setq p1(list (- (car c0) l6) (+ (cadr c0) l5)))
  (setq p2(list (+ (car c0) l6) (+ (cadr c0) l5)))
  (setq p3(list (car p2) (- (cadr p2) l3)))
  (setq p4(list (- (car p3) (- l6 l1)) (cadr p3)))
  (setq p5(list (car p4) (- (cadr p4) (- l4 l3))))
  (setq p8(list (car p1) (cadr p3)))
  (setq p7(list (+ (car p8) (- l6 l1)) (cadr p8)))
  (setq p6(list (car p7) (cadr p5)))
  (command "line" p1 p2 p3 p4 p5 p6 p7 p8 "c")
  (command "dim" "hor" p1 c0 c2 "" "vert" p2 p3 c2 "" "hor" p3 p4 c2 "" "exit")
  (command "zoom" "all")
  )
