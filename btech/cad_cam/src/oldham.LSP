;program for genrate coupling for various diameter
;command :oldham
(defun dtr (a)
(/ (* a pi) 180.0)
)


;get dimension
(defun getdata3 ()
(command "erase" "all" "" )  
(setq p1 (getpoint "\n enter the lower left corner:"))
(setq power (getreal "\n give the power in H.P.:"))  
(setq N (getreal "\n give the rpm of shaft:"))
)


;making coupling
(defun oldham ()
(setq p 85.0)
(setq torque (/ (* power 4500.0) (* 2.0 p N)))
(setq d (* 100.00 (expt (/(* 3 torque ) (* power 1.8) (/ 1.0 3.0)))))
(setq p2 (polar p1 (dtr 0) (* d 2.5)))
(setq p3 (polar p2 (dtr 90) (* d 0.5)))
(setq p4 (polar p2 (dtr 90) d))
(setq p5 (polar p4 (dtr 180) (* d 1.75)))        
(setq p6 (polar p5 (dtr 90) d))
(setq p7 (polar p6 (dtr 180) (* d 0.75)))
(setq p8 (polar p7 (dtr 270) (* d 1.5)))
(command "-layer" "s" "0"  "" )
(command "view" "top")
(command "-osnap" "off")
(command "shademode" "2d" )  
(command "pline" p3 p4 p5 p6 p7 p8 p3 "")
(setq e1 (entlast))
(command "revolve" e1 "" p1 p2 "360.0" )
(setq e2 (entlast))
(command "zoom" "e" )
)


;making of disc
(defun disc ()
(setq d1 (polar p1 (dtr 180) (* d 2.0)))
(setq d2 (polar d1 (dtr 90) (* d 2.0)))
(setq d3 (polar d2 (dtr 180) (/ (* d 0.45)2.0)))
(setq d4 (polar d3 (dtr 270) (* d 2.0)))
(command "pline" d1 d2 d3 d4 d1 "")
(setq t1 (entlast))
(command "revolve" t1 "" d1 d4 "-360.0" )
(setq t2 (entlast))
(setq k1 (polar d1 (dtr 90) (/ (* d 0.45) 2.0)))
(setq k2 (polar k1 (dtr 0) (/ (* d 0.45) 2.0)))
(setq k3 (polar k2 (dtr 270) (* d 0.45)))
(setq k4 (polar k3 (dtr 180) (/ (* d 0.45) 2.0)))
(command "pline" k1 k2 k3 k4 k1 "")
(setq h1 (entlast))
(command "extrude" h1 "" (* d 2.0) "0" )
(setq h2 (entlast))  
(command "pline" k1 k2 k3 k4 k1 "")
(setq h3 (entlast))
(command "extrude" h3 "" (-(* d 2.0)) "0" )
(setq h4 (entlast))
(command "union" h2 h4 "")
(setq h5 (entlast))
(command "copy" h5 "" d1 p1 )
(setq h6 (entlast))
(setq k5 (polar d3 (dtr 180) (/ (* d 0.45) 2.0)))
(setq k6 (polar k5 (dtr 270) (* d 4.0)))
(setq k7 (polar k6 (dtr 0) (/ (* d 0.45) 2.0)))
(command "pline" d3 k5 k6 k7 d3 "")
(setq h7 (entlast))
(command "extrude" h7 "" (/ (* d 0.45) 2.0) "0" )
(setq h8 (entlast))  
(command "pline" d3 k5 k6 k7 d3 "")
(setq h9 (entlast))
(command "extrude" h9 "" (-(/ (* d 0.45) 2.0)) "0" )
(setq h10 (entlast))
(command "union" h8 h10 "")
(setq h11 (entlast))
(setq m1 (polar d4 (dtr 180) (/ (* d 5.35) 2.0)))
(command "mirror" e2 "" k5 k6 "")
(setq h12 (entlast))
(command "copy" h11 "" d4 m1 )
(setq h13 (entlast))
(command "subtract" h12 "" h13 "")
(setq e4 (entlast)) 
(command "subtract" e2 "" h6"")
(setq e3 (entlast))
(command "union" t2 h5 h11 "")
(setq h14 (entlast))
(command "zoom" "e" )  
(command "view" "nwiso")  
)


;For assemblling parts
(defun assemblly()
(setq a1 (polar d1 (dtr 0) (* d 2.0)))
(setq a2 (polar d4 (dtr 180 ) (/ (* d 5.35 )2.0)))
(setq s1 (polar p2 (dtr 180) (* d 2.0)))
(command "move" e2 "" p2 s1 )
(command "move" h12 "" m1 d4 )
(setq chk 5)
(while (> chk 0)
(setq str1 (getstring "\nChange_dim\\Oldham\\Disc\\Shade\\disassaMble\\Text\\dEsign data\\eXit:"))
(if(=(strcase str1) "O")
(oldham)
(if(=(strcase str1) "D")
(disc)
(if(=(strcase str1) "C")
(getdata3)
(if(=(strcase str1) "T")
(text3)
(if(=(strcase str1) "E")
(data3)  
(if(=(strcase str1) "S")
(shade2)    
(if(=(strcase str1) "X")
(out)
(if(=(strcase str1) "M")
(disassemblly)
)
)
)
)
)
)
)
)
)
)


;for disassemble
(defun disassemblly()
(setq a1 (polar d1 (dtr 0) (* d 2.0)))
(setq a2 (polar d4 (dtr 180 ) (/ (* d 5.35 )2.0)))
(setq s1 (polar p2 (dtr 180) (* d 2.0)))
(command "move" e2 "" s1 p2)
(command "move" h12 "" d4 m1)
(setq chk 5)
(while (> chk 0)
(setq str2 (getstring "\nChange_dim\\Oldham\\Disc\\Shade\\Assamblly\\Text\\dEsign data\\eXit:"))
(if(=(strcase str2) "O")
(oldham)
(if(=(strcase str2) "D")
(disc)
(if(=(strcase str2) "C")
(getdata3)
(if(=(strcase str2) "T")
(text3)
(if(=(strcase str2) "E")
(data3)  
(if(=(strcase str2) "S")
(shade2)    
(if(=(strcase str2) "X")
(out)
(if(=(strcase str2) "A")
(assemblly)
)
)
)
)
)
)
)
)
)
)


;design data
(defun data3 ()
(setq g01 (getstring "\n (** FOR DESIGN DATA PRESS F2 KEY **) "))
(princ g01)
(setq g0 (getstring "\n All Dimensions are in cm "))
(princ g0)  
(setq g (getstring "\n Dia of shaft   d:"))
(princ g)
(princ d)
(setq g5 (getstring "\n Material of Coupling is Cast Iron whose
                          \n permissible pressure is 85kg/cm2  :")) 
(princ g5)
(setq g6 (getstring "\n Torque Transmitted by shaft    T :"))
(princ g6)
(princ torque)
(setq g9 (getstring "\n Power transmitted in hp    Power :"))
(princ g9)
(princ power)
(setq g10 (getstring "\n Speed of shaft in rpm    N :"))
(princ g10)
(princ N)
)


; text 
(defun text3()
(setq z (/ d 6.0))
(command "ucs" "n" "v")
(setq text1 (getpoint "\n enter the corner point of text :"))
(command "-layer" "n" "text" "c" 51 "text" "s" "text" "" )
(command "text" text1 z "0"
           "OLDHAM COUPLING DESIGNED BY :- "
	   "")
(command "text" "" "PRASHANT KUMAR JAIN" 
	   "")
(command "text" "" "LECTURER (Mech. & Auto. Engg." 
	   "")
(command "text"	""  "MAIT, ROHINI, DELHI-85"
	   "")
(command "-layer" "s" "0"  "" )
(command "zoom" "e")
(command "ucs" "w")
)


;shade
(defun shade2()
(command "ucs" "w"  )
(command "change" e2 "" "p" "c" 160 "")
(command "change" h12 "" "p" "c" 12 "")
(command "change" t2 h5 h11 "" "p" "c" 41 "")  
(command "shademode" "g")
)

    
; for exit drawing
(defun out ()
(setvar "blipmode" sblip)
(setvar "cmdecho" scmde)
(setq chk 0)
(princ)
)


;menu definition
(defun menu3 ()
(getdata3)
(setq chk 5)
(while (> chk 0)
(setq xxx (getstring "\n Change_dim\\Oldham\\Disc\\Assemblly\\Shade\\Text\\dEsign data\\eXit:"))
(if(=(strcase xxx) "O")
(oldham)
(if(=(strcase xxx) "D")
(disc)
(if(=(strcase xxx) "T")
(text3)
(if(=(strcase xxx) "C")
(getdata3)
(if(=(strcase xxx) "A")
(assemblly)
(if(=(strcase xxx) "E")
(data3)  
(if(=(strcase xxx) "S")
(shade2)    
(if(=(strcase xxx) "X")
(out)
)
)
)
)
)
)
)
)
)
)


;main
(defun c:oldham ()
(setq sblip (getvar "blipmode" ))
(setq scmde (getvar "cmdecho"))
(setvar "blipmode" 0)
(setvar "cmdecho" 0)
(menu3)
)
;end programe
