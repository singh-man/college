Attribute VB_Name = "UserForm1"
Attribute VB_Base = "0{9B627DA0-4D48-4071-8802-C7D81730D578}{7BA60F25-74BB-463B-9230-A813EC606238}"
Attribute VB_GlobalNameSpace = False
Attribute VB_Creatable = False
Attribute VB_PredeclaredId = True
Attribute VB_Exposed = False
Attribute VB_TemplateDerived = False
Attribute VB_Customizable = False
Private Sub CommandButton1_Click()
UserForm1.hide
Dim aq As Acad3DSolid
Dim a1 As Acad3DSolid
Dim p1(0 To 2) As Double
Dim p2(0 To 2) As Double
Dim p3(0 To 2) As Double
Dim p4(0 To 2) As Double
Dim p5(0 To 2) As Double
Dim NewDirection(0 To 2) As Double
Dim l As Double
Dim w As Double
Dim h As Double
Dim h1 As Double
p1(0) = 0: p1(1) = 0: p1(2) = 0
With ThisDrawing.Utility
l = .GetDistance(p1, "enter length")
w = .GetDistance(p1, "enter width")


End With
h = 15
l1 = 15
w1 = 15
h1 = ThisDrawing.Utility.GetDistance(p1, "enter height")
p2(0) = -l / 2 + 15 / 2: p2(1) = -w / 2 + 15 / 2: p2(2) = -h1 / 2 + 5
p3(0) = -l / 2 + 15 / 2: p3(1) = w / 2 - 15 / 2: p3(2) = -h1 / 2 + 5
p4(0) = l / 2 - 15 / 2: p4(1) = -w / 2 + 15 / 2: p4(2) = -h1 / 2 + 5
p5(0) = l / 2 - 15 / 2: p5(1) = w / 2 - 15 / 2: p5(2) = -h1 / 2 + 5
Set aq = ThisDrawing.ModelSpace.AddBox(p1, l, w, h)
aq.Update
Set a1 = ThisDrawing.ModelSpace.AddBox(p2, l1, w1, h1)
a1.Update
Set a2 = ThisDrawing.ModelSpace.AddBox(p3, l1, w1, h1)
a2.Update
Set a3 = ThisDrawing.ModelSpace.AddBox(p4, l1, w1, h1)
a3.Update
Set a4 = ThisDrawing.ModelSpace.AddBox(p5, l1, w1, h1)
a4.Update

NewDirection(0) = -1: NewDirection(1) = -1: NewDirection(2) = 1
ThisDrawing.ActiveViewport.Direction = NewDirection
ThisDrawing.ActiveViewport = ThisDrawing.ActiveViewport
Unload Me
End Sub
